module topology-update {
    yang-version 1;
    namespace "urn:opendaylight:params:xml:ns:yang:topology-update";
    prefix "topology-update";

    revision "2015-01-05" {
        description "Initial revision of topology-update model";
    }
}

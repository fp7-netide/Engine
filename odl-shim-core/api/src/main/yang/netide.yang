module netide {
    yang-version 1;
    namespace "urn:opendaylight:params:xml:ns:yang:netide";
    prefix "netide";

    revision "2015-01-05" {
        description "Initial revision of netide model";
    }
}

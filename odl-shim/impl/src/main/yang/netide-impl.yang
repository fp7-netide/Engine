module netide-impl {
    yang-version 1;
    namespace "urn:opendaylight:params:xml:ns:yang:netide:netide-impl";
    prefix "netide-impl";

    import config { prefix config; revision-date 2013-04-05; }
    import opendaylight-md-sal-binding { prefix md-sal-binding; revision-date 2013-10-28;}
    import openflow-configuration {prefix of-config; revision-date 2014-06-30; }
    import ietf-inet-types {prefix ietf-inet; revision-date 2010-09-24; }
    import opendaylight-sal-binding-broker-impl { prefix sal-broker; revision-date 2013-10-28;}
    
    description
        "Service definition for hello project";

    revision "2015-10-01" {
        description
            "Initial revision";
    }

    identity netide-impl {
        base config:module-type;
        config:java-name-prefix NetideMain;
    }

    augment "/config:modules/config:module/config:configuration" {
        case netide-impl {
            when "/config:modules/config:module/config:type = 'netide-impl'";
            
            leaf core-address {
                description "address of Core";
                type ietf-inet:ip-address;
                mandatory true;
            }
            
            leaf core-port {
                description "port of Core";  
                type int32;
                mandatory true;
            }
            
            leaf port {
                description "local listening port";
                type uint16;
                mandatory true;
            }
            leaf address {
                description "address of local listening interface";
                type ietf-inet:ip-address;
                mandatory true;
            }
            leaf transport-protocol {
                description "Transport protocol used for communication.";
                type of-config:transport-protocol;
                mandatory true;
            }
            leaf switch-idle-timeout {
                description "idle timeout in [ms]";
                type uint32;
                mandatory true;
            }
            container tls {
                leaf keystore {
                    description "keystore location";
                    type string;
                }
                leaf keystore-type {
                    description "keystore type (JKS or PKCS12)";
                    type of-config:keystore-type;
                }
                leaf keystore-path-type {
                    description "keystore path type (CLASSPATH or PATH)";
                    type of-config:path-type;
                }
                leaf keystore-password {
                    description "password protecting keystore";
                    type string;
                }
                leaf certificate-password {
                    description "password protecting certificate";
                    type string;
                }
                leaf truststore {
                    description "truststore location";
                    type string;
                }
                leaf truststore-type {
                    description "truststore type (JKS or PKCS12)";
                    type of-config:keystore-type;
                }
                leaf truststore-path-type {
                    description "truststore path type (CLASSPATH or PATH)";
                    type of-config:path-type;
                }
                leaf truststore-password {
                    description "password protecting truststore";
                    type string;
                }
            }
            container threads {
                leaf boss-threads {
                    type uint16;
                }
                leaf worker-threads {
                    type uint16;
                }
            }
            
            container broker {
                uses config:service-ref {
                    refine type {
                        mandatory true;
                        config:required-identity md-sal-binding:binding-broker-osgi-registry;
                    }
                }
            }
            
            container notification-adapter {
                uses config:service-ref {
                    refine type {
                        mandatory true;
                        config:required-identity sal-broker:binding-new-notification-service;
                    }
                }
            }
            container notification-publish-adapter {
                uses config:service-ref {
                    refine type {
                        mandatory true;
                        config:required-identity sal-broker:binding-new-notification-publish-service;
                    }
                }
            }
        }
        
    }
}
